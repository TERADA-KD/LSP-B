;;高圧機器　単線図の入力各種
;;==================================================================================================
;; 1.OCR 単線図の入力    S1OCR.LSP     2005/NOV  by T.Terada
;;==================================================================================================
(defun C:S1OCR( / DAT RETU GYO Rasc SEL1 SEL PFX VCBT)
    (setq *error* *err1*)
    (setvar "CMDECHO" 1)(setvar "BLIPMODE" 0)
    (DCL_OCR)
    (C:MKR)               ;; 基本メーカーを調べる
;;メーカー番号の決定
    (if (= MAKER "0")(setq MN "1")) (if (= MAKER "1")(setq MN "4"))
    (if (= MAKER "2")(setq MN "1")) (if (= MAKER "3")(setq MN "4"))
;;EXCELの読込み開始"列"を決定
    (if (or (= MAKER "0")(= MAKER "2"))(progn (setq RETU "E") (setq Rasc (ascii "E")))) ;三菱の場合
    (if (or (= MAKER "1")(= MAKER "3"))(progn (setq RETU "AE")(setq Rasc (ascii "AE"))));富士の場合
;   (princ "\n列=")(princ RETU) (princ "\n行=")(princ GYO)
;;OCR
    (if (= VCBT "手動")
        (setq GYO "12") ;手動 = 電流引はずし
        (setq GYO "11") ;電動 = 電圧引はずし ;else
    )
    (setq DAT nil)
    (if (= (strlen RETU) 2)(setq PFX  (substr RETU 1 1)));(princ "\nPFX=")(princ PFX)
        (xls_open "X:/XLS/高圧機器一覧表" "r")
           (repeat 15 
              (setq SEL1 (strcat RETU GYO))
              (setq SEL (xls_getval SEL1));;     (princ "\nCEL=")(princ SEL1)
              (setq DAT (append DAT (list SEL)))
              (if (= (strlen RETU) 2)
                  (progn ;;                      (princ "\n列=")(princ RETU)
                      (setq RETU (substr RETU 2 1))
                      (setq RETU (strcat PFX (chr (+ (ascii RETU) 1))))
                  )
              )
              (if (= (strlen RETU) 1)(setq RETU (chr (+ (ascii RETU) 1))))
           )
        (xls_close);(princ DAT)
     (setq PNO (getstring "\n機器番号を指示:(例：-1)"))
    (cond ((= PNO "") (setq PNO "-1")))(setq PNO (strcat "OCR" PNO))
     (prompt "\n挿入点を指示")
    (command "INSERT" (nth 1 DAT) pause "1" "1" "0" (nth 0 DAT) PNO    (nth 2 DAT) (nth 3 DAT) (nth 4 DAT)
                                               (nth 5 DAT) (nth 6 DAT) (nth 7 DAT) (nth 8 DAT) (nth 9 DAT)
                                               (nth 10 DAT)(nth 11 DAT)(nth 12 DAT)(nth 13 DAT)(nth 14 DAT)
    )
      (redraw)(setvar "CMDECHO" 1)(setvar "BLIPMODE" 1)
)
;-------------------
(defun DCL_OCR (/ DEF DEF_BAK WHAT_NEXT)
      (setq DEF nil)(setq DEF_BAK DEF)(if (not DEF)(setq DEF "1"))
      (setq DCL_ID (load_dialog "/LSP-I/KD.DCL"))(setq WHAT_NEXT 2)
      (while (>= WHAT_NEXT 2)
          (if (null (new_dialog "S1OCR" DCL_ID) )(exit)) 
          (action_tile "cancel" "(done_dialog)(exit)")
          (action_tile "1" "(setq DEF $key)")
          (action_tile "2" "(setq DEF $key)")
          (setq WHAT_NEXT (start_dialog))
      )
      (unload_dialog DCL_ID)(princ)
      (cond ((= WHAT_NEXT 0)(setq DEF DEF_BAK))
            ((= WHAT_NEXT 1) DEF)
      )
      (cond ((= DEF "1")(setq VCBT "手動"))((= DEF "2")(setq VCBT "電動")))
)
;;==================================================================================================
;; 2.HGR 単線図の入力    S1HGR.LSP     2005/NOV  by T.Terada
;;==================================================================================================
(defun C:S1HGR( / DAT RETU GYO Rasc SEL1 SEL PFX VCBT)
    (setq *error* *err1*)
    (setvar "CMDECHO" 1)(setvar "BLIPMODE" 0)
    (DCL_HGR)
    (C:MKR)               ;; 基本メーカーを調べる
;;メーカー番号の決定
    (if (= MAKER "0")(setq MN "1")) (if (= MAKER "1")(setq MN "4"))
    (if (= MAKER "2")(setq MN "1")) (if (= MAKER "3")(setq MN "4"))
;;EXCELの読込み開始"列"を決定
    (if (or (= MAKER "0")(= MAKER "2"))(progn (setq RETU "E") (setq Rasc (ascii "E")))) ;三菱の場合
    (if (or (= MAKER "1")(= MAKER "3"))(progn (setq RETU "AE")(setq Rasc (ascii "AE"))));富士の場合
;   (princ "\n列=")(princ RETU) (princ "\n行=")(princ GYO)
;;HGR
    (if (= VCBT "手動")
        (setq GYO "14") ;手動 = 電流引はずし
        (setq GYO "13") ;電動 = 電圧引はずし ;else
    )
    (setq DAT nil)
    (if (= (strlen RETU) 2)(setq PFX  (substr RETU 1 1)));(princ "\nPFX=")(princ PFX)
        (xls_open "X:/XLS/高圧機器一覧表" "r")
           (repeat 15 
              (setq SEL1 (strcat RETU GYO))
              (setq SEL (xls_getval SEL1));;     (princ "\nCEL=")(princ SEL1)
              (setq DAT (append DAT (list SEL)))
              (if (= (strlen RETU) 2)
                  (progn ;;                      (princ "\n列=")(princ RETU)
                      (setq RETU (substr RETU 2 1))
                      (setq RETU (strcat PFX (chr (+ (ascii RETU) 1))))
                  )
              )
              (if (= (strlen RETU) 1)(setq RETU (chr (+ (ascii RETU) 1))))
           )
        (xls_close);(princ DAT)
     (setq PNO (getstring "\n機器番号を指示:(例：-1)"))
    (cond ((= PNO "") (setq PNO "-1")))(setq PNO (strcat "OCR" PNO))
     (prompt "\n挿入点を指示")
    (command "INSERT" (nth 1 DAT) pause "1" "1" "0" (nth 0 DAT) PNO    (nth 2 DAT) (nth 3 DAT) (nth 4 DAT)
                                               (nth 5 DAT) (nth 6 DAT) (nth 7 DAT) (nth 8 DAT) (nth 9 DAT)
                                               (nth 10 DAT)(nth 11 DAT)(nth 12 DAT)(nth 13 DAT)(nth 14 DAT)
    )
      (redraw)(setvar "CMDECHO" 1)(setvar "BLIPMODE" 1)
)
;-------------------
(defun DCL_HGR (/ DEF DEF_BAK WHAT_NEXT)
      (setq DEF nil)(setq DEF_BAK DEF)(if (not DEF)(setq DEF "1"))
      (setq DCL_ID (load_dialog "X:/LSP-I/KD.DCL"))(setq WHAT_NEXT 2)
      (while (>= WHAT_NEXT 2)
          (if (null (new_dialog "S1OCR" DCL_ID) )(exit)) 
          (action_tile "cancel" "(done_dialog)(exit)")
          (action_tile "1" "(setq DEF $key)")
          (action_tile "2" "(setq DEF $key)")
          (setq WHAT_NEXT (start_dialog))
      )
      (unload_dialog DCL_ID)(princ)
      (cond ((= WHAT_NEXT 0)(setq DEF DEF_BAK))
            ((= WHAT_NEXT 1) DEF)
      )
      (cond ((= DEF "1")(setq VCBT "手動"))((= DEF "2")(setq VCBT "電動")))
)
;;==================================================================================================
;; 3.各種機器 単線図の入力    S1X.LSP     2005/NOV  by T.Terada
;;   DGR,UVR,OVR,VG,ZPD,APFC,CTD,2E,3E,SET,A-TD,V-TD,W-TD,PF-TD,Var-TD,HZ-TD,VT,LA1,LA3,OP-MCB
;;   実行前に右記で機器名を、設定する事。 ===> (setq KIKI "APFC")
;;   挿入されるシンボル名称は、高圧機器一覧表.XLSのSYM覧が参照されます。
;;==================================================================================================
(defun C:S1X( / DAT RETU GYO Rasc SEL1 SEL PFX VCBT)
    (setq *error* *err1*)
    (setvar "CMDECHO" 0)
    (setvar "BLIPMODE" 0)
    (C:MKR)               ;; 基本メーカーを調べる
;;メーカー番号の決定
    (if (= MAKER "0")(setq MN "1")) (if (= MAKER "1")(setq MN "4"))
    (if (= MAKER "2")(setq MN "1")) (if (= MAKER "3")(setq MN "4"))
;;EXCELの読込み開始"列"を決定
    (if (or (= MAKER "0")(= MAKER "2"))(progn (setq RETU "E") (setq Rasc (ascii "E")))) ;三菱の場合
    (if (or (= MAKER "1")(= MAKER "3"))(progn (setq RETU "AE")(setq Rasc (ascii "AE"))));富士の場合
;   (princ "\n列=")(princ RETU) (princ "\n行=")(princ GYO)
;;機種の選定
    (if (= KIKI "DGR")   (setq GYO "15"))
    (if (= KIKI "UVR")   (setq GYO "16"))
    (if (= KIKI "OVR")   (setq GYO "17"))
    (if (= KIKI "VG")    (setq GYO "18"))
    (if (= KIKI "ZPD")   (setq GYO "19"))
    (if (= KIKI "APFC")  (setq GYO "20"))
    (if (= KIKI "CTD")   (setq GYO "27"))
    (if (= KIKI "2E")    (setq GYO "28"))
    (if (= KIKI "3E")    (setq GYO "29"))
    (if (= KIKI "SET")   (setq GYO "30"))
    (if (= KIKI "A-TD")  (setq GYO "31"))
    (if (= KIKI "V-TD")  (setq GYO "32"))
    (if (= KIKI "W-TD")  (setq GYO "33"))
    (if (= KIKI "PF-TD") (setq GYO "34"))
    (if (= KIKI "Var-TD")(setq GYO "35"))
    (if (= KIKI "HZ-TD") (setq GYO "36"))
    (if (= KIKI "VT")    (setq GYO "37"))
    (if (= KIKI "LA1")   (setq GYO "44"))
    (if (= KIKI "LA3")   (setq GYO "45"))
    (if (= KIKI "OP-MCB")(setq GYO "46"))
    
    
    (setq DAT nil)
    (if (= (strlen RETU) 2)(setq PFX  (substr RETU 1 1)));(princ "\nPFX=")(princ PFX)
        (xls_open "X:/XLS/高圧機器一覧表" "r")
           (repeat 15 
              (setq SEL1 (strcat RETU GYO))
              (setq SEL (xls_getval SEL1));;     (princ "\nCEL=")(princ SEL1)
              (setq DAT (append DAT (list SEL)))
              (if (= (strlen RETU) 2)
                  (progn ;;                      (princ "\n列=")(princ RETU)
                      (setq RETU (substr RETU 2 1))
                      (setq RETU (strcat PFX (chr (+ (ascii RETU) 1))))
                  )
              )
              (if (= (strlen RETU) 1)(setq RETU (chr (+ (ascii RETU) 1))))
           )
        (xls_close);(princ DAT)
     (setq PNO (getstring "\n機器番号を指示:(例：-1)"))
    (cond ((= PNO "") (setq PNO "-1")))(setq PNO (strcat (nth 0 DAT) PNO))
     (prompt "\n挿入点を指示")
    (command "INSERT" (nth 1 DAT) pause "1" "1" "0" (nth 0 DAT) PNO    (nth 2 DAT) (nth 3 DAT) (nth 4 DAT)
                                               (nth 5 DAT) (nth 6 DAT) (nth 7 DAT) (nth 8 DAT) (nth 9 DAT)
                                               (nth 10 DAT)(nth 11 DAT)(nth 12 DAT)(nth 13 DAT)(nth 14 DAT)
    )
      (redraw)(setvar "CMDECHO" 1)(setvar "BLIPMODE" 1)
)
;;==================================================================================================
;; 4.DS 単線図の入力    S1DS.LSP     2005/NOV  by T.Terada
;;==================================================================================================
(defun C:S1DS( / DAT RETU GYO Rasc SEL1 SEL PFX VCBT)
    (setq *error* *err1*)
    (setvar "CMDECHO" 1)(setvar "BLIPMODE" 0)
    (DCL_DS)
    (C:MKR)               ;; 基本メーカーを調べる
;;メーカー番号の決定
    (if (= MAKER "0")(setq MN "1")) (if (= MAKER "1")(setq MN "4"))
    (if (= MAKER "2")(setq MN "1")) (if (= MAKER "3")(setq MN "4"))
;;EXCELの読込み開始"列"を決定
    (if (or (= MAKER "0")(= MAKER "2"))(progn (setq RETU "E") (setq Rasc (ascii "E")))) ;三菱の場合
    (if (or (= MAKER "1")(= MAKER "3"))(progn (setq RETU "AE")(setq Rasc (ascii "AE"))));富士の場合
    (setq DAT nil);(princ "\n列=")(princ RETU) (princ "\n行=")(princ GYO)
    (if (= (strlen RETU) 2)(setq PFX  (substr RETU 1 1)));(princ "\nPFX=")(princ PFX)
        (xls_open "X:/XLS/高圧機器一覧表" "r")
           (repeat 15 
              (setq SEL1 (strcat RETU GYO))
              (setq SEL (xls_getval SEL1));;     (princ "\nCEL=")(princ SEL1)
              (setq DAT (append DAT (list SEL)))
              (if (= (strlen RETU) 2)
                  (progn ;;                      (princ "\n列=")(princ RETU)
                      (setq RETU (substr RETU 2 1))
                      (setq RETU (strcat PFX (chr (+ (ascii RETU) 1))))
                  )
              )
              (if (= (strlen RETU) 1)(setq RETU (chr (+ (ascii RETU) 1))))
           )
        (xls_close);(princ DAT)
     (setq PNO (getstring "\n機器番号を指示:(例：-1)"))
    (cond ((= PNO "") (setq PNO "-1")))(setq PNO (strcat "OCR" PNO))
     (prompt "\n挿入点を指示")
    (command "INSERT" (nth 1 DAT) pause "1" "1" "0" (nth 0 DAT) PNO    (nth 2 DAT) (nth 3 DAT) (nth 4 DAT)
                                               (nth 5 DAT) (nth 6 DAT) (nth 7 DAT) (nth 8 DAT) (nth 9 DAT)
                                               (nth 10 DAT)(nth 11 DAT)(nth 12 DAT)(nth 13 DAT)(nth 14 DAT)
    )
      (redraw)(setvar "CMDECHO" 1)(setvar "BLIPMODE" 1)
)
;-------------------
(defun DCL_DS (/)
      (setq DCL_ID (load_dialog "X:/LSP-I/KD.DCL"))
      (if (not (new_dialog "S1DS" DCL_ID) )(exit)) 
          (action_tile "cancel" "(done_dialog)(exit)")
          (action_tile "11" "(setq GYO \"161\")")
          (action_tile "12" "(setq GYO \"162\")")
          (action_tile "13" "(setq GYO \"163\")")
          (action_tile "14" "(setq GYO \"164\")")
          (action_tile "21" "(setq GYO \"165\")")
          (action_tile "22" "(setq GYO \"166\")")
          (action_tile "23" "(setq GYO \"167\")")
          (action_tile "24" "(setq GYO \"168\")")
          (action_tile "31" "(setq GYO \"169\")")
          (action_tile "32" "(setq GYO \"170\")")
          (action_tile "33" "(setq GYO \"171\")")
          (action_tile "34" "(setq GYO \"172\")")
      (start_dialog)(unload_dialog DCL_ID)(princ)
)
;;==================================================================================================
;; 5.TT 試験端子の単線図入力    S1TT.LSP     2005/NOV  by T.Terada
;;==================================================================================================
(defun C:S1TT( / DAT RETU GYO Rasc SEL1 SEL PFX VCBT)
    (setq *error* *err1*)
    (setvar "CMDECHO" 0)(setvar "BLIPMODE" 0)
    (DCL_TT)
    (C:MKR)               ;; 基本メーカーを調べる
;;メーカー番号の決定
    (if (= MAKER "0")(setq MN "1")) (if (= MAKER "1")(setq MN "4"))
    (if (= MAKER "2")(setq MN "1")) (if (= MAKER "3")(setq MN "4"))
;;EXCELの読込み開始"列"を決定
    (if (or (= MAKER "0")(= MAKER "2"))(progn (setq RETU "E") (setq Rasc (ascii "E")))) ;三菱の場合
    (if (or (= MAKER "1")(= MAKER "3"))(progn (setq RETU "AE")(setq Rasc (ascii "AE"))));富士の場合
    (setq DAT nil);(princ "\n列=")(princ RETU) (princ "\n行=")(princ GYO)
    (if (= (strlen RETU) 2)(setq PFX  (substr RETU 1 1)));(princ "\nPFX=")(princ PFX)
        (xls_open "X:/XLS/高圧機器一覧表" "r")
           (repeat 15 
              (setq SEL1 (strcat RETU GYO))
              (setq SEL (xls_getval SEL1));;     (princ "\nCEL=")(princ SEL1)
              (setq DAT (append DAT (list SEL)))
              (if (= (strlen RETU) 2)
                  (progn ;;                      (princ "\n列=")(princ RETU)
                      (setq RETU (substr RETU 2 1))
                      (setq RETU (strcat PFX (chr (+ (ascii RETU) 1))))
                  )
              )
              (if (= (strlen RETU) 1)(setq RETU (chr (+ (ascii RETU) 1))))
           )
        (xls_close);(princ DAT)
     (setq PNO (getstring "\n機器番号を指示:(例：-1)"))
    (cond ((= PNO "") (setq PNO "-1")))(setq PNO (strcat "T-TT" PNO))
     (prompt "\n挿入点を指示")
    (command "INSERT" (nth 1 DAT) pause "1" "1" "0" (nth 0 DAT) PNO    (nth 2 DAT) (nth 3 DAT) (nth 4 DAT)
                                               (nth 5 DAT) (nth 6 DAT) (nth 7 DAT) (nth 8 DAT) (nth 9 DAT)
                                               (nth 10 DAT)(nth 11 DAT)(nth 12 DAT)(nth 13 DAT)(nth 14 DAT)
    )
      (redraw)(setvar "CMDECHO" 1)(setvar "BLIPMODE" 1)
)
;-------------------
(defun DCL_TT (/)
      (setq DCL_ID (load_dialog "X:/LSP-I/KD.DCL"))
      (if (not (new_dialog "S1TT" DCL_ID) )(exit)) 
          (action_tile "cancel" "(done_dialog)(exit)")
          (action_tile "11" "(setq GYO \"21\")")
          (action_tile "12" "(setq GYO \"22\")")
          (action_tile "13" "(setq GYO \"23\")")
          (action_tile "21" "(setq GYO \"24\")")
          (action_tile "22" "(setq GYO \"25\")")
          (action_tile "23" "(setq GYO \"26\")")
      (start_dialog)(unload_dialog DCL_ID)(princ)
)
;;==================================================================================================
;; 6.高圧ＺＣＴ の単線図入力    S1HZCTM.LSP S1HZCTF    2005/NOV  by T.Terada
;;==================================================================================================
(defun C:S1HZCT( / DAT RETU GYO Rasc SEL1 SEL PFX MN PNO)
    (setq *error* *err1*)
    (setvar "CMDECHO" 0)(setvar "BLIPMODE" 0)
    (C:MKR)               ;; 基本メーカーを調べる
;;メーカー番号の決定
    (if (= MAKER "0")(setq MN "1")) (if (= MAKER "1")(setq MN "4"))
    (if (= MAKER "2")(setq MN "1")) (if (= MAKER "3")(setq MN "4"))
    (if (= MN "1")(DCL_ZCTHM))
    (if (= MN "4")(DCL_ZCTHF))
;;EXCELの読込み開始"列"を決定
    (if (or (= MAKER "0")(= MAKER "2"))(progn (setq RETU "E") (setq Rasc (ascii "E")))) ;三菱の場合
    (if (or (= MAKER "1")(= MAKER "3"))(progn (setq RETU "AE")(setq Rasc (ascii "AE"))));富士の場合
    (setq DAT nil);(princ "\n列=")(princ RETU) (princ "\n行=")(princ GYO)
    (if (= (strlen RETU) 2)(setq PFX  (substr RETU 1 1)));(princ "\nPFX=")(princ PFX)
        (xls_open "X:/XLS/高圧機器一覧表" "r")
           (repeat 15 
              (setq SEL1 (strcat RETU GYO))
              (setq SEL (xls_getval SEL1));;     (princ "\nCEL=")(princ SEL1)
              (setq DAT (append DAT (list SEL)))
              (if (= (strlen RETU) 2)
                  (progn ;;                      (princ "\n列=")(princ RETU)
                      (setq RETU (substr RETU 2 1))
                      (setq RETU (strcat PFX (chr (+ (ascii RETU) 1))))
                  )
              )
              (if (= (strlen RETU) 1)(setq RETU (chr (+ (ascii RETU) 1))))
           )
        (xls_close);(princ DAT)
     (setq PNO (getstring "\n機器番号を指示:(例：-1)"))
    (cond ((= PNO "") (setq PNO "-1")))(setq PNO (strcat "ZCT" PNO))
     (prompt "\n挿入点を指示")
    (command "INSERT" (nth 1 DAT) pause "1" "1" "0" (nth 0 DAT) PNO    (nth 2 DAT) (nth 3 DAT) (nth 4 DAT)
                                               (nth 5 DAT) (nth 6 DAT) (nth 7 DAT) (nth 8 DAT) (nth 9 DAT)
                                               (nth 10 DAT)(nth 11 DAT)(nth 12 DAT)(nth 13 DAT)(nth 14 DAT)
    )
    (redraw)(setvar "CMDECHO" 1)(setvar "BLIPMODE" 1)
)
;-------------------
(defun DCL_ZCTHM (/);三菱
      (setq DCL_ID (load_dialog "X:/LSP-I/KD.DCL"))
      (if (not (new_dialog "S1HZCTM" DCL_ID) )(exit)) 
          (action_tile "cancel" "(done_dialog)(exit)")
          (action_tile "11" "(setq GYO \"141\")")
          (action_tile "12" "(setq GYO \"142\")")
          (action_tile "13" "(setq GYO \"143\")")
          (action_tile "14" "(setq GYO \"144\")")
          (action_tile "15" "(setq GYO \"145\")")
          (action_tile "16" "(setq GYO \"146\")")
          (action_tile "21" "(setq GYO \"147\")")
          (action_tile "22" "(setq GYO \"148\")")
          (action_tile "23" "(setq GYO \"149\")")
      (start_dialog)(unload_dialog DCL_ID)(princ)
)
;-------------------
(defun DCL_ZCTHF (/);富士
      (setq DCL_ID (load_dialog "X:/LSP-I/KD.DCL"))
      (if (not (new_dialog "S1HZCTF" DCL_ID) )(exit)) 
          (action_tile "cancel" "(done_dialog)(exit)")
          (action_tile "11" "(setq GYO \"141\")")
          (action_tile "12" "(setq GYO \"142\")")
          (action_tile "13" "(setq GYO \"143\")")
          (action_tile "14" "(setq GYO \"144\")")
          (action_tile "15" "(setq GYO \"145\")")
          (action_tile "21" "(setq GYO \"147\")")
          (action_tile "22" "(setq GYO \"148\")")
      (start_dialog)(unload_dialog DCL_ID)(princ)
)
;;==================================================================================================
;; 7.電流計の単線図入力    S1AM.LSP     2005/NOV  by T.Terada
;;==================================================================================================
(defun C:S1AM( / DAT RETU GYO Rasc SEL1 SEL PFX VCBT)
 ;   (setq *error* *err1*)
    (setvar "CMDECHO" 1)(setvar "BLIPMODE" 0)
    (DCL_AM)
    (DCL_AMR)
    (C:MKR)               ;; 基本メーカーを調べる
;;メーカー番号の決定
    (if (= MAKER "0")(setq MN "1")) (if (= MAKER "1")(setq MN "4"))
    (if (= MAKER "2")(setq MN "1")) (if (= MAKER "3")(setq MN "4"))
;;EXCELの読込み開始"列"を決定
    (if (or (= MAKER "0")(= MAKER "2"))(progn (setq RETU "E") (setq Rasc (ascii "E")))) ;三菱の場合
    (if (or (= MAKER "1")(= MAKER "3"))(progn (setq RETU "AE")(setq Rasc (ascii "AE"))));富士の場合
    (setq DAT nil);(princ "\n列=")(princ RETU) (princ "\n行=")(princ GYO)
    (if (= (strlen RETU) 2)(setq PFX  (substr RETU 1 1)));(princ "\nPFX=")(princ PFX)
        (xls_open "X:/XLS/高圧機器一覧表" "r")
           (repeat 15 
              (setq SEL1 (strcat RETU GYO))
              (setq SEL (xls_getval SEL1));;     (princ "\nCEL=")(princ SEL1)
              (setq DAT (append DAT (list SEL)))
              (if (= (strlen RETU) 2)
                  (progn ;;                      (princ "\n列=")(princ RETU)
                      (setq RETU (substr RETU 2 1))
                      (setq RETU (strcat PFX (chr (+ (ascii RETU) 1))))
                  )
              )
              (if (= (strlen RETU) 1)(setq RETU (chr (+ (ascii RETU) 1))))
           )
        (xls_close);(princ DAT)
     (setq PNO (getstring "\n機器番号を指示:(例：-1)"))
    (cond ((= PNO "") (setq PNO "-1")))(setq PNO2 (strcat "AS" PNO))(setq PNO (strcat "AM" PNO))
     (prompt "\n挿入点を指示")
    (command "INSERT" (nth 1 DAT) pause "1" "1" "0" (nth 0 DAT) PNO    (nth 2 DAT) T2 T3
                                               (nth 5 DAT) (nth 6 DAT) (nth 7 DAT) (nth 8 DAT) (nth 9 DAT)
                                               (nth 10 DAT)(nth 11 DAT)(nth 12 DAT)(nth 13 DAT)(nth 14 DAT)
    )
    (setq PC (getvar "LASTPOINT"))
    (if (= AS "Y")
        (progn
           (setq PC (list (- (car PC) 100)(cadr PC)))
           (command "INSERT" "QAS" PC "1" "1" "0" "AS" PNO2 "BHN-A" "" "銘板N-1" "" "" "" "" "" "" "14" "1" "" "")
        )
    )
    (redraw)(setvar "CMDECHO" 1)(setvar "BLIPMODE" 1)
)
;-------------------
(defun DCL_AM (/)
      (setq DCL_ID (load_dialog "X:/LSP-I/KD.DCL"))
      (if (not (new_dialog "S1AM" DCL_ID) )(exit)) 
          (action_tile "cancel" "(done_dialog)(exit)")
          (action_tile "11" "(setq GYO \"61\")")
          (action_tile "12" "(setq GYO \"62\")")
          (action_tile "13" "(setq GYO \"64\")")
          (action_tile "14" "(setq GYO \"63\")")
          (action_tile "15" "(setq GYO \"65\")")
          (action_tile "21" "(setq GYO \"61\")(setq AS \"Y\")")
          (action_tile "22" "(setq GYO \"62\")(setq AS \"Y\")")
          (action_tile "31" "(setq T2  \"赤指針付き\")")
      (start_dialog)(unload_dialog DCL_ID)(princ)
)
(defun DCL_AMR (/)
      (setq DCL_ID (load_dialog "/LSP-I/KD.DCL"))
      (if (not (new_dialog "S1AMR" DCL_ID) )(exit)) 
          (action_tile "cancel" "(done_dialog)(exit)")   
          (action_tile "T5A"   "(setq T3 \"0～5/5A\")")   (action_tile "T300A"  "(setq T3 \"0～300/5A\")")
          (action_tile "T10A"  "(setq T3 \"0～10/5A\")")  (action_tile "T400A"  "(setq T3 \"0～400/5A\")")
          (action_tile "T15A"  "(setq T3 \"0～15/5A\")")  (action_tile "T500A"  "(setq T3 \"0～500/5A\")")
          (action_tile "T20A"  "(setq T3 \"0～20/5A\")")  (action_tile "T600A"  "(setq T3 \"0～600/5A\")")
          (action_tile "T30A"  "(setq T3 \"0～30/5A\")")  (action_tile "T750A"  "(setq T3 \"0～750/5A\")")
          (action_tile "T40A"  "(setq T3 \"0～40/5A\")")  (action_tile "T800A"  "(setq T3 \"0～800/5A\")")
          (action_tile "T50A"  "(setq T3 \"0～50/5A\")")  (action_tile "T1000A" "(setq T3 \"0～1000/5A\")")
          (action_tile "T60A"  "(setq T3 \"0～60/5A\")")  (action_tile "T1200A" "(setq T3 \"0～1200/5A\")")
          (action_tile "T75A"  "(setq T3 \"0～75/5A\")")  (action_tile "T1500A" "(setq T3 \"0～1500/5A\")")
          (action_tile "T80A"  "(setq T3 \"0～80/5A\")")  (action_tile "T2000A" "(setq T3 \"0～2000/5A\")")
          (action_tile "T100A" "(setq T3 \"0～100/5A\")") (action_tile "T2500A" "(setq T3 \"0～2500/5A\")")
          (action_tile "T120A" "(setq T3 \"0～120/5A\")") (action_tile "T3000A" "(setq T3 \"0～3000/5A\")")
          (action_tile "T150A" "(setq T3 \"0～150/5A\")") (action_tile "T4000A" "(setq T3 \"0～4000/5A\")")
          (action_tile "T200A" "(setq T3 \"0～200/5A\")") (action_tile "T5000A" "(setq T3 \"0～5000/5A\")")
          (action_tile "T250A" "(setq T3 \"0～250/5A\")") 
      (start_dialog)(unload_dialog DCL_ID)(princ)
)
